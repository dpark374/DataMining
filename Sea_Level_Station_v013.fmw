FME workspace Sea_Level_Station_v013.fmw

Parameters:
- SourceDataset_XLSXR = $(FME_MF_DIR)Sea_Level_Station_Index_2020.xlsx   # Source Microsoft Excel File(s)
- DestDataset_POSTGIS = Dev   # Connection
- SourceDataset_CSV2 = $(FME_MF_DIR)tide_stations_2019.csv   # Source CSV (Comma Separated Value) File(s)
- DestDataset_XLSXW_3 = $(FME_MF_DIR)Tide_station_Update.xlsx   # Destination Microsoft Excel File
- DestDataset_POSTGIS_3 = Post_Prod   # Connection

Readers:
- XLSXR_1: XLSXR from $(SourceDataset_XLSXR)
- CSV2_1: CSV2 from $(SourceDataset_CSV2)

Writers:
- POSTGIS_1: POSTGIS to $(DestDataset_POSTGIS)
- XLSXW_1: XLSXW to $(DestDataset_XLSXW_3)
- POSTGIS_2: POSTGIS to $(DestDataset_POSTGIS_3)

Note: tide-stations: Sea_Level_Station_Index_2020 [XLSXR]
tide-stations (reader XLSXR_1)
    attributes: WKT char(27), WKT.formatting boolean, id number(5,0), id.formatting boolean, location char(53), location.formatting boolean, latitude y_coordinate, latitude.formatting boolean, longitude x_coordinate, longitude.formatting boolean, ref_stn char(14), ref_stn.formatting boolean, tg_bm char(15), tg_bm.formatting boolean, cd_to_bm number(6,3), cd_to_bm.formatting boolean, mhws number(5,2), mhws.formatting boolean, mhwn number(5,2), mhwn.formatting boolean, mlwn number(5,2), mlwn.formatting boolean, mlws number(5,2), mlws.formatting boolean, msl number(5,2), msl.formatting boolean, hat number(5,2), hat.formatting boolean, lat number(5,2), lat.formatting boolean,
      data_start number(9,0), data_start.formatting boolean, data_end date, data_end.formatting boolean, data_len number(8,3), data_len.formatting boolean, owner char(40), owner.formatting boolean, gauge_type char(33), gauge_type.formatting boolean, pred_link char(65), pred_link.formatting boolean, data_link char(101), data_link.formatting boolean, int_number char(6), int_number.formatting boolean, shape_X number(9,4), shape_X.formatting boolean, shape_Y number(9,4), shape_Y.formatting boolean, Z string, Z.formatting boolean
    -> AttributeCreator
    -> ChangeDetector [REVISED]
Note: CSV: tide_stations_2019 [CSV2]
CSV (reader CSV2_1)
    attributes: id uint16, location string, latitude y_coordinate, longitude x_coordinate, ref_stn string, tg_bm string, cd_to_bm real32, mhws real32, mhwn real32, mlwn real32, mlws real32, msl real32, hat real32, lat real32, data_start string, data_end string, data_len real32, owner string, gauge_type string, pred_link string, data_link string, int_number string
    -> ChangeDetector [ORIGINAL]
CoordinateExtractor
    IND = 0
    MODE = Specify Coordinate
    X_ATTR = _x
    Z_DEFAULT = 0
    -> TestFilter
TestFilter
    DEFAULT_VALUE = <UNFILTERED>
    TEST_LIST = "BOOL_OP,OR,COMPOSITE_TEST,""""""1"""""",TEST_CLAUSE,TEST @Value(_x) < 0",@Value(_x) < 0,"BOOL_OP,OR,COMPOSITE_TEST,""""""1"""""",TEST_CLAUSE,TEST @Value(_x) > 360",@Value(_x) > 360
    @Value(_x) < 0 -> Offsetter
    @Value(_x) > 360 -> Offsetter_2
    <UNFILTERED> -> AttributeManager
Offsetter
    MODE = Cartesian Coordinate
    XOFF = 360
    YOFF = 0
    ZOFF = 0
    OFFSET -> AttributeManager
Offsetter_2
    MODE = Cartesian Coordinate
    XOFF = -360
    YOFF = 0
    ZOFF = 0
    OFFSET -> AttributeManager
AttributeManager
    ATTR_TABLE:
      REMOVE WKT.formatting
      REMOVE id.formatting
      REMOVE location.formatting
      REMOVE latitude.formatting
      REMOVE longitude.formatting
      REMOVE ref_stn.formatting
      REMOVE tg_bm.formatting
      REMOVE cd_to_bm.formatting
      REMOVE mhws.formatting
      REMOVE mhwn.formatting
      REMOVE mlwn.formatting
      REMOVE mlws.formatting
      REMOVE msl.formatting
      REMOVE hat.formatting
      REMOVE lat.formatting
      REMOVE data_start.formatting
      REMOVE data_end.formatting
      REMOVE data_len.formatting
      REMOVE owner.formatting
      REMOVE gauge_type.formatting
      REMOVE pred_link.formatting
      REMOVE data_link.formatting
      REMOVE int_number.formatting
      REMOVE shape_X.formatting
      REMOVE shape_Y.formatting
      REMOVE Z.formatting
      REMOVE _x
    -> DateTimeStamper
DateTimeStamper
    DATETIME_ATTR = _timestamp
    STAMP_TYPE = date
    TIMEZONE = utc
    -> AttributeFilter
AttributeFilter
    ATTR_NAME = CHANGES
    ATTR_VALUES = <Empty>,<Missing>,<Null>,<Unfiltered>,DELETED,Update,New
    <EMPTY> -> AttributeManager_3
    <EMPTY> -> Sheet1 (writer XLSXW_1)
    <MISSING> -> AttributeManager_3
    <MISSING> -> Sheet1 (writer XLSXW_1)
    DELETED -> Sheet1 (writer XLSXW_1)
    Update -> AttributeManager_3
    Update -> Sheet1 (writer XLSXW_1)
    New -> AttributeManager_3
    New -> Sheet1 (writer XLSXW_1)
AttributeManager_3
    ATTR_TABLE:
      REMOVE CHANGES
      REMOVE WKT
      SET_TO data_start = @DateTimeFormat(@Value(data_start),%d/%m/%y)
      SET_TO data_end =  @DateTimeFormat(@Value(data_end),%d/%m/%y)
      REMOVE shape_Y
      REMOVE shape_X
      REMOVE Z
      REMOVE fme_geometry
      REMOVE _timestamp
    -> Inspector
Inspector
Note: tide_stations_2020: Dev [POSTGIS]
tide_stations_2020 (writer POSTGIS_1)
    attributes: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

Bookmark: Data compare
AttributeCreator
    ATTR_TABLE = SET_TO CHANGES = FME_CONDITIONAL:DEFAULT_VALUE'_FME_NO_OP_'BOOL_OP;OR;COMPOSITE_TEST;1;TEST @Value(id.formatting)@Value(location.formatting)@Value(WKT.formatting)@Value(tg_bm.formatting) = version;1;font_color;1,0,0version;1;font_color;1,0,0version;1;font_color;1,0,0version;1;font_color;1,0,0'New'BOOL_OP;OR;COMPOSITE_TEST;1;TEST @Value(id.formatting) = version;1;font_color;1,0,0'Update'BOOL_OP;OR;COMPOSITE_TEST;1;TEST @Value(WKT.formatting) = version;1;font_color;1,0,0'Update'BOOL_OP;OR;COMPOSITE_TEST;1;TEST @Value(location.formatting) = version;1;font_color;1,0,0'Update'BOOL_OP;OR;COMPOSITE_TEST;1;TEST @Value(ref_stn.formatting) = version;1;font_color;1,0,0'Update'BOOL_OP;OR;COMPOSITE_TEST;1;TEST @Value(tg_bm.formatting) = version;1;font_color;1,0,0'Update'BOOL_OP;OR;COMPOSITE_TEST;1;TEST @Value(cd_to_bm.formatting) = version;1;font_color;1,0,0'Update'BOOL_OP;OR;COMPOSITE_TEST;1;TEST @Value(mhws.formatting) = version;1;font_color;1,0,0'Update'BOOL_OP;OR;COMPOSITE_TEST;1;TEST @Value(mlwn.formatting) = version;1;font_color;1,0,0'Update'BOOL_OP;OR;COMPOSITE_TEST;1;TEST @Value(mlws.formatting) = version;1;font_color;1,0,0'Update'BOOL_OP;OR;COMPOSITE_TEST;1;TEST @Value(msl.formatting) = version;1;font_color;1,0,0'Update'BOOL_OP;OR;COMPOSITE_TEST;1;TEST @Value(data_start.formatting) = version;1;font_color;1,0,0;number_format_string;LibXLStandardFormat14'Update'BOOL_OP;OR;COMPOSITE_TEST;1;TEST @Value(data_end.formatting) = version;1;font_color;1,0,0;number_format_string;LibXLStandardFormat14'Update'BOOL_OP;OR;COMPOSITE_TEST;1;TEST @Value(data_len.formatting) = version;1;font_color;1,0,0'Upddate'BOOL_OP;OR;COMPOSITE_TEST;1;TEST @Value(owner.formatting) = version;1;font_color;1,0,0'Update'BOOL_OP;OR;COMPOSITE_TEST;1;TEST @Value(gauge_type.formatting) = version;1;font_color;1,0,0'Update'BOOL_OP;OR;COMPOSITE_TEST;1;TEST @Value(pred_link.formatting) = version;1;font_color;1,0,0'Update'BOOL_OP;OR;COMPOSITE_TEST;1;TEST @Value(int_number.formatting) = version;1;font_color;1,0,0'Update'BOOL_OP;OR;COMPOSITE_TEST;1;TEST @Value(shape_X.formatting) = version;1;font_color;1,0,0'Update'BOOL_OP;OR;COMPOSITE_TEST;1;TEST @Value(shape_Y.formatting) = version;1;font_color;1,0,0'update'FME_NUM_CONDITIONS21___
    -> AttributeManager_2
ChangeDetector
    BLANK_AND_MISSING_DIFFER = No
    CHECK_TYPES_AND_ENCODINGS = No
    MATCHATTRS = id
    MATCH_STRATEGY = Match Selected Attributes
    UNCHANGED_OUTPUT = Output Original
    DELETED -> AttributeCreator_2
AttributeCreator_2
    ATTR_TABLE = SET_TO CHANGES = DELETED
    -> AttributeManager_2
AttributeManager_2
    ATTR_TABLE:
      SET_TO gauge_type = FME_CONDITIONAL:DEFAULT_VALUE'_FME_NO_OP_'BOOL_OP;OR;COMPOSITE_TEST;1;TEST @Value(gauge_type.formatting) = version;1;font;Calibri,STRIKEOUT;font_color;1,0,0''FME_NUM_CONDITIONS2___
      SET_TO data_link = FME_CONDITIONAL:DEFAULT_VALUE'_FME_NO_OP_'BOOL_OP;OR;COMPOSITE_TEST;1;TEST @Value(data_link.formatting) = version;1;font;Calibri,STRIKEOUT''FME_NUM_CONDITIONS2___
    -> CoordinateExtractor

Bookmark: Update Report
Note: : Tide_station_Update [XLSXW]
Sheet1 (writer XLSXW_1)
    attributes: CHANGES string(200), WKT string(27), id number(20), location string(20), latitude number(20), longitude number(20), ref_stn string(20), tg_bm string(20), cd_to_bm number(20), mhws number(20), mhwn number(20), mlwn number(20), mlws number(20), msl number(20), hat number(20), lat number(20), data_start string(20), data_end string(20), data_len number(20), owner string(20), gauge_type string(20), pred_link string(20), data_link string(20), int_number string(20), shape_X number(9), shape_Y number(9), Z string(20), _timestamp string(20)

Bookmark: Prod conn
Note: tide_station_2021: Post_Prod [POSTGIS]
tide_stations (writer POSTGIS_2)
    attributes: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
